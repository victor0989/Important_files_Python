# -*- coding: utf-8 -*-
# Macro FreeCAD: Direct Fusion Drive con propulsor modular integrado
# Autor: Víctor + Copilot
# Unidades: mm, eje longitudinal = X

import FreeCAD as App, FreeCADGui as Gui, Part, math

doc_name = "Direct_Fusion_Drive"
if App.ActiveDocument is None or App.ActiveDocument.Label != doc_name:
    App.newDocument(doc_name)
doc = App.ActiveDocument

# ============
# Parámetros
# ============
P = {
    # Fuselaje
    "nose_len": 800.0, "nose_base_d": 600.0,
    "mid_len": 1400.0, "mid_d": 900.0,
    "rear_len": 800.0, "rear_d": 1200.0,
    "hull_t": 10.0,

    # Cabina
    "cockpit_w": 900.0, "cockpit_h": 400.0, "cockpit_l": 600.0, "cockpit_x0": 600.0,

    # Ventanas
    "win_w": 600.0, "win_h": 250.0, "win_th": 20.0,
    "win_y_off": 0.5*(900.0/2.0 - 250.0/2.0), "win_z": 0.0,

    # Reactor
    "reactor_d": 800.0, "reactor_l": 900.0, "reactor_cx": 2600.0,
    "ring_h": 30.0, "ring_ro": 420.0, "ring_ri": 380.0, "ring_n": 6, "ring_pitch": 150.0,

    # Coils
    "coil_rect_w": 80.0, "coil_rect_h": 80.0, "coil_R": 440.0,
    "coil_n": 4, "coil_span": 800.0,

    # Blindajes
    "moderator_t": 100.0, "moderator_gap": 20.0, "moderator_over": 200.0,
    "tungsten_post_t": 10.0,

    # Boquilla
    "nozzle_throat_d": 300.0, "nozzle_exit_d": 900.0, "nozzle_l": 700.0,
    "nozzle_cx": 2850.0, "nozzle_fillet_r": 40.0,

    # Truss boquilla
    "truss_n": 3, "truss_tube_w": 80.0, "truss_R_attach": 550.0,

    # Tanques
    "tank_d": 300.0, "tank_l": 700.0, "tank_cx": 1600.0, "tank_cy": 300.0, "tank_cz": -150.0,

    # Tren
    "leg_L_fold": 400.0, "leg_L_ext": 600.0, "leg_foot_d": 180.0,
    "leg_side_x1": 1050.0, "leg_side_x2": 1950.0, "leg_side_y": 600.0,
    "leg_front_x": 400.0, "leg_front_y": 0.0, "leg_front_z": -(900.0/2.0) + 50.0,

    # Alas / empenaje
    "wing_root_w": 600.0, "wing_tip_w": 150.0, "wing_chord": 450.0,
    "fin_h": 400.0, "fin_base": 200.0,

    # Propulsor modular
    "prop_cx": 3000.0, "prop_cy": 0.0, "prop_cz": 0.0
}

# ============
# Utilidades
# ============
X_AXIS = App.Vector(1,0,0)
Y_AXIS = App.Vector(0,1,0)
Z_AXIS = App.Vector(0,0,1)

def rot_to_x(): return App.Rotation(Y_AXIS, 90)
def add_obj(shape, label): o = doc.addObject("Part::Feature", label); o.Shape = shape; return o

def make_cyl_x(d, L, cx=0.0, cy=0.0, cz=0.0, label="CylX"):
    r = d/2.0
    cyl = Part.makeCylinder(r, L)
    cyl.Placement = App.Placement(App.Vector(cx - L/2.0, cy, cz), rot_to_x())
    return add_obj(cyl, label)

def make_cone_x(d1, d2, L, cx=0.0, cy=0.0, cz=0.0, label="ConeX"):
    r1, r2 = d1/2.0, d2/2.0
    cone = Part.makeCone(r1, r2, L)
    cone.Placement = App.Placement(App.Vector(cx - L/2.0, cy, cz), rot_to_x())
    return add_obj(cone, label)

def make_torus_x(R, r, cx=0.0, cy=0.0, cz=0.0, label="TorusX"):
    tor = Part.makeTorus(R, r)
    tor.Placement = App.Placement(App.Vector(cx, cy, cz), rot_to_x())
    return add_obj(tor, label)

def make_box(w, d, h, cx=0.0, cy=0.0, cz=0.0, label="Box"):
    b = Part.makeBox(w, d, h)
    b.Placement = App.Placement(App.Vector(cx - w/2.0, cy - d/2.0, cz - h/2.0), App.Rotation())
    return add_obj(b, label)

def make_hollow_from_offset(outer_shape, t, label="Shell"):
    try:
        inner = outer_shape.makeOffsetShape(-t, 0.01, join=2, fill=True)
        shell = outer_shape.cut(inner)
        return add_obj(shell, label)
    except:
        return add_obj(outer_shape, label + "_fallback")

# ============
# Fuselaje base
# ============
nose = make_cone_x(P["nose_base_d"], 0.0, P["nose_len"], cx=P["nose_len"]/2.0, label="Nose")
mid  = make_cyl_x(P["mid_d"], P["mid_len"], cx=P["nose_len"] + P["mid_len"]/2.0, label="Mid")
rear = make_cyl_x(P["rear_d"], P["rear_len"], cx=P["nose_len"] + P["mid_len"] + P["rear_len"]/2.0, label="Rear")

fuse_fuselage_shape = nose.Shape.fuse(mid.Shape).fuse(rear.Shape)
hull = make_hollow_from_offset(fuse_fuselage_shape, P["hull_t"], label="Hull_Shell")

# ============
# Cabina y ventanas
# ============
cockpit = make_box(P["cockpit_w"], P["cockpit_l"], P["cockpit_h"], cx=P["cockpit_x0"] + P["cockpit_l"]/2.0, cy=0.0, cz=0.0, label="Cockpit")
# Ventanas: simplificadas como recortes
win_left = make_box(P["win_w"], P["win_th"], P["win_h"], cx=P["cockpit_x0"] + P["cockpit_l"]/2.0, cy=-P["cockpit_w"]/2.0 + P["win_y_off"] + P["win_h"]/2.0, cz=P["win_z"], label="Win_Left")
win_right = make_box(P["win_w"], P["win_th"], P["win_h"], cx=P["cockpit_x0"] + P["cockpit_l"]/2.0, cy=P["cockpit_w"]/2.0 - P["win_y_off"] - P["win_h"]/2.0, cz=P["win_z"], label="Win_Right")
cockpit.Shape = cockpit.Shape.cut(win_left.Shape).cut(win_right.Shape)

# ============
# Reactor
# ============
reactor = make_cyl_x(P["reactor_d"], P["reactor_l"], cx=P["reactor_cx"], label="Reactor")
# Anillos
rings = []
for i in range(P["ring_n"]):
    z = P["reactor_cx"] - P["reactor_l"]/2.0 + P["ring_pitch"] * (i + 0.5)
    ring = make_torus_x(P["ring_ro"], P["ring_h"]/2.0, cx=z, label=f"Ring_{i}")
    rings.append(ring)
# Bobinas
coils = []
for i in range(P["coil_n"]):
    angle = 360.0 / P["coil_n"] * i
    coil = make_box(P["coil_rect_w"], P["coil_rect_h"], P["coil_span"], cx=P["reactor_cx"], cy=P["coil_R"] * math.cos(math.radians(angle)), cz=P["coil_R"] * math.sin(math.radians(angle)), label=f"Coil_{i}")
    coil.Placement = App.Placement(coil.Placement.Base, App.Rotation(Z_AXIS, angle))
    coils.append(coil)

# ============
# Blindajes
# ============
moderator_outer = make_cyl_x(P["reactor_d"] + 2*P["moderator_over"], P["reactor_l"] + 2*P["moderator_over"], cx=P["reactor_cx"], label="Moderator_Outer")
moderator_inner = make_cyl_x(P["reactor_d"] + 2*P["moderator_gap"], P["reactor_l"] + 2*P["moderator_gap"], cx=P["reactor_cx"], label="Moderator_Inner")
moderator = moderator_outer.Shape.cut(moderator_inner.Shape)
moderator_obj = add_obj(moderator, "Moderator")

# Tungsten posts: simplificados como cilindros
tungsten_posts = []
for i in range(6):
    angle = 60 * i
    post = make_cyl_x(P["tungsten_post_t"], P["reactor_l"], cx=P["reactor_cx"], cy=(P["reactor_d"]/2.0 + P["moderator_gap"]) * math.cos(math.radians(angle)), cz=(P["reactor_d"]/2.0 + P["moderator_gap"]) * math.sin(math.radians(angle)), label=f"Tungsten_Post_{i}")
    tungsten_posts.append(post)

# ============
# Boquilla
# ============
nozzle = make_cone_x(P["nozzle_throat_d"], P["nozzle_exit_d"], P["nozzle_l"], cx=P["nozzle_cx"], label="Nozzle")
# Truss: simplificado como tubos
truss_tubes = []
for i in range(P["truss_n"]):
    angle = 360.0 / P["truss_n"] * i
    tube = make_cyl_x(P["truss_tube_w"], P["nozzle_l"], cx=P["nozzle_cx"], cy=P["truss_R_attach"] * math.cos(math.radians(angle)), cz=P["truss_R_attach"] * math.sin(math.radians(angle)), label=f"Truss_{i}")
    truss_tubes.append(tube)

# ============
# Tanques
# ============
tank = make_cyl_x(P["tank_d"], P["tank_l"], cx=P["tank_cx"], cy=P["tank_cy"], cz=P["tank_cz"], label="Tank")

# ============
# Tren de aterrizaje
# ============
legs = []
# Piernas laterales
for side in [-1, 1]:
    leg = make_cyl_x(P["leg_foot_d"], P["leg_L_ext"], cx=P["leg_side_x1"], cy=side * P["leg_side_y"], cz=-P["leg_L_ext"]/2.0, label=f"Leg_Side_{side}")
    legs.append(leg)
    leg2 = make_cyl_x(P["leg_foot_d"], P["leg_L_ext"], cx=P["leg_side_x2"], cy=side * P["leg_side_y"], cz=-P["leg_L_ext"]/2.0, label=f"Leg_Side2_{side}")
    legs.append(leg2)
# Pierna frontal
leg_front = make_cyl_x(P["leg_foot_d"], P["leg_L_ext"], cx=P["leg_front_x"], cy=P["leg_front_y"], cz=P["leg_front_z"] - P["leg_L_ext"]/2.0, label="Leg_Front")
legs.append(leg_front)

# ============
# Alas y empenaje
# ============
# Alas: trapezoidales
wing_left = Part.makePolygon([
    App.Vector(P["nose_len"] + P["mid_len"]/2.0 - P["wing_chord"]/2.0, -P["wing_root_w"]/2.0, 0),
    App.Vector(P["nose_len"] + P["mid_len"]/2.0 + P["wing_chord"]/2.0, -P["wing_tip_w"]/2.0, 0),
    App.Vector(P["nose_len"] + P["mid_len"]/2.0 + P["wing_chord"]/2.0, P["wing_tip_w"]/2.0, 0),
    App.Vector(P["nose_len"] + P["mid_len"]/2.0 - P["wing_chord"]/2.0, P["wing_root_w"]/2.0, 0),
    App.Vector(P["nose_len"] + P["mid_len"]/2.0 - P["wing_chord"]/2.0, -P["wing_root_w"]/2.0, 0)
])
wing_left = Part.Face(wing_left).extrude(App.Vector(0,0,P["hull_t"]))
wing_left_obj = add_obj(wing_left, "Wing_Left")

wing_right = wing_left.mirror(App.Vector(0,0,0), App.Vector(0,1,0))
wing_right_obj = add_obj(wing_right, "Wing_Right")

# Empenaje vertical
fin = make_box(P["fin_base"], P["fin_h"], P["hull_t"], cx=P["nose_len"] + P["mid_len"] + P["rear_len"] - P["fin_base"]/2.0, cy=0.0, cz=P["fin_h"]/2.0, label="Fin")

# ============
# Escudos de carbono y ablativos
# ============
# Escudo de carbono: capa delgada alrededor del casco
carbon_shield_outer = fuse_fuselage_shape.makeOffsetShape(5.0, 0.01, join=2, fill=True)  # 5mm offset
carbon_shield_inner = fuse_fuselage_shape.makeOffsetShape(3.0, 0.01, join=2, fill=True)  # 3mm inner
carbon_shield = carbon_shield_outer.cut(carbon_shield_inner)
carbon_shield_obj = add_obj(carbon_shield, "Carbon_Shield")

# Escudo ablativo: cono grueso en la nariz
ablative_shield = make_cone_x(P["nose_base_d"] + 50.0, P["nose_base_d"], P["nose_len"]/2.0, cx=P["nose_len"]/4.0, label="Ablative_Shield")

# ============
# Nuevas funcionalidades: paneles solares y antenas
# ============
# Paneles solares: dos paneles planos en la parte superior
solar_panel_l = 600.0
solar_panel_w = 400.0
solar_panel_t = 5.0
solar_left = make_box(solar_panel_l, solar_panel_w, solar_panel_t, cx=P["nose_len"] + P["mid_len"]/2.0, cy=-P["mid_d"]/2.0 - solar_panel_w/2.0, cz=P["mid_d"]/2.0 + solar_panel_t/2.0, label="Solar_Left")
solar_right = make_box(solar_panel_l, solar_panel_w, solar_panel_t, cx=P["nose_len"] + P["mid_len"]/2.0, cy=P["mid_d"]/2.0 + solar_panel_w/2.0, cz=P["mid_d"]/2.0 + solar_panel_t/2.0, label="Solar_Right")

# Antenas: cilindros pequeños en la parte superior
antenna_h = 200.0
antenna_d = 10.0
antenna1 = make_cyl_x(antenna_d, antenna_h, cx=P["nose_len"] + P["mid_len"]/4.0, cy=0.0, cz=P["mid_d"]/2.0 + antenna_h/2.0, label="Antenna1")
antenna2 = make_cyl_x(antenna_d, antenna_h, cx=P["nose_len"] + 3*P["mid_len"]/4.0, cy=P["mid_d"]/4.0, cz=P["mid_d"]/2.0 + antenna_h/2.0, label="Antenna2")
antenna3 = make_cyl_x(antenna_d, antenna_h, cx=P["nose_len"] + 3*P["mid_len"]/4.0, cy=-P["mid_d"]/4.0, cz=P["mid_d"]/2.0 + antenna_h/2.0, label="Antenna3")

# ============
# Propulsor modular
# ============
def make_propulsor_modular(cx, cy, cz, label_prefix="Propulsor"):
    parts = []
    # Cámara principal
    camara = Part.makeCylinder(200, 400)
    camara.Placement = App.Placement(App.Vector(cx - 200, cy, cz), rot_to_x())
    parts.append(camara)
    # Anillos estructurales
    for i in range(3):
        ring = Part.makeTorus(110, 10)
        ring.Placement = App.Placement(App.Vector(cx - 150 + i*150, cy, cz), rot_to_x())
        parts.append(ring)
    # Boquilla
    nozzle = Part.makeCone(100, 250, 300)
    nozzle.Placement = App.Placement(App.Vector(cx + 200, cy, cz), rot_to_x())
    parts.append(nozzle)
    # Unión
    shape = parts[0]
    for p in parts[1:]:
        shape = shape.fuse(p)
    return add_obj(shape, f"{label_prefix}_Asm")

propulsor_obj = make_propulsor_modular(P["prop_cx"], P["prop_cy"], P["prop_cz"])

# Cortar casco para encaje del propulsor
hull.Shape = hull.Shape.cut(propulsor_obj.Shape)

# ============
# Ensamblaje final
# ============
asm = doc.addObject("App::Part", "DFD_Ship")
parts_to_add = [hull, cockpit, reactor, moderator_obj, nozzle, tank, wing_left_obj, wing_right_obj, fin, carbon_shield_obj, ablative_shield, solar_left, solar_right, antenna1, antenna2, antenna3, propulsor_obj]
parts_to_add.extend(rings)
parts_to_add.extend(coils)
parts_to_add.extend(tungsten_posts)
parts_to_add.extend(truss_tubes)
parts_to_add.extend(legs)
for o in parts_to_add:
    asm.addObject(o)

doc.recompute()
try:
    Gui.ActiveDocument.ActiveView.viewAxonometric()
except:
    pass
