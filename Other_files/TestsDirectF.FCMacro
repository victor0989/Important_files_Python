# -*- coding: utf-8 -*-
# Macro FreeCAD: Nave Espacial Direct Fusion Drive con TPS Avanzado, Blindaje de Radiación y Características Espaciales
# Autor: Asistente AI + Usuario
# Unidades: mm, eje longitudinal = X

import FreeCAD as App, FreeCADGui as Gui, Part, math

doc_name = "Direct_Fusion_Spaceship"
if App.ActiveDocument is None or App.ActiveDocument.Label != doc_name:
    App.newDocument(doc_name)
doc = App.ActiveDocument

# ========================
# Parámetros escalados para nave espacial grande
# ========================
P = {
    "nose_len": 3200.0, "nose_base_d": 2400.0,
    "mid_len": 5600.0, "mid_d": 3600.0,
    "rear_len": 3200.0, "rear_d": 4800.0,
    "hull_t": 50.0,  # grueso para impresión 3D
    "cockpit_w": 3600.0, "cockpit_h": 1600.0, "cockpit_l": 2400.0, "cockpit_x0": 2400.0,
    "win_w": 2400.0, "win_h": 1000.0, "win_th": 80.0,
    "reactor_d": 3200.0, "reactor_l": 3600.0, "reactor_cx": 10400.0,
    "ring_h": 120.0, "ring_ro": 1680.0, "ring_ri": 1520.0, "ring_n": 6, "ring_pitch": 600.0,
    "coil_rect_w": 320.0, "coil_rect_h": 320.0, "coil_R": 1760.0, "coil_n": 4, "coil_span": 3200.0,
    "moderator_t": 400.0, "moderator_gap": 80.0, "moderator_over": 800.0,
    "tungsten_post_t": 40.0,
    "nozzle_throat_d": 1200.0, "nozzle_exit_d": 3600.0, "nozzle_l": 2800.0, "nozzle_cx": 12800.0,
    "truss_n": 3, "truss_tube_w": 320.0, "truss_R_attach": 2200.0,
    "tank_d": 1200.0, "tank_l": 2800.0, "tank_cx": 6400.0, "tank_cy": 1200.0, "tank_cz": -600.0,
    "wing_root_w": 2400.0, "wing_tip_w": 600.0, "wing_chord": 1800.0,
    "fin_h": 1600.0, "fin_base": 800.0,
    "rad_panel_w": 3200.0, "rad_panel_h": 2400.0, "rad_panel_n": 5
}

# TPS avanzado
TPS = {"tps_d": 9600.0, "tps_t": 400.0, "tps_gap": 480.0, "sup_L": 1120.0, "sup_d_base": 3600.0, "sup_d_tip": 2400.0}
RAD = {"th": 16.0, "mount_gap_y": 120.0, "x_start": None, "gap_x": None, "count_pairs": 10, "span_x": 880.0, "arm_len": 240.0, "arm_r": 40.0}

# ========================
# Materiales avanzados resistentes
# ========================
MAT = {
    'TITANIUM': {'name': 'Ti-6Al-4V', 'rho': 4430.0, 'E': 114e9, 'nu': 0.32, 'type': 'isotropic'},
    'CARBON_FIBER': {'name': 'Carbon Fiber Composite', 'rho': 1600.0, 'Ex': 200e9, 'Ey': 10e9, 'Ez': 10e9, 'nu_xy': 0.25, 'type': 'orthotropic'},
    'ABLATIVE': {'name': 'Ablative TPS', 'rho': 1200.0, 'Ex': 50e9, 'Ey': 50e9, 'Ez': 5e9, 'nu_xy': 0.2, 'type': 'orthotropic'},
    'LEAD': {'name': 'Lead', 'rho': 11340.0, 'E': 16e9, 'nu': 0.44, 'type': 'isotropic'},
    'STEEL': {'name': 'SS-304', 'rho': 8000.0, 'E': 200e9, 'nu': 0.30, 'type': 'isotropic'},
    'COPPER': {'name': 'Copper', 'rho': 8960.0, 'E': 110e9, 'nu': 0.34, 'type': 'isotropic'}
}

# ========================
# Utilidades
# ========================
X_AXIS = App.Vector(1, 0, 0)
Y_AXIS = App.Vector(0, 1, 0)
Z_AXIS = App.Vector(0, 0, 1)

def rot_to_x():
    return App.Rotation(Y_AXIS, 90)

def add_obj(shape, label):
    obj = doc.addObject("Part::Feature", label)
    obj.Shape = shape
    return obj

def set_mat(obj, mat):
    if not obj: return
    m = MAT.get(mat, None)
    if not m: return
    obj.addProperty("App::PropertyString", "Material", "Meta", "").Material = m.get('name', '')
    obj.addProperty("App::PropertyMap", "MaterialData", "Meta", "").MaterialData = {k: str(v) for k, v in m.items()}
    obj.addProperty("App::PropertyFloat", "Density", "Meta", "").Density = m.get('rho', 0.0)

def make_cyl_x(d, L, cx=0.0, cy=0.0, cz=0.0, label="CylX"):
    r = d / 2.0
    cyl = Part.makeCylinder(r, L)
    cyl.Placement = App.Placement(App.Vector(cx - L/2.0, cy, cz), rot_to_x())
    return add_obj(cyl, label)

def make_cone_x(d1, d2, L, cx=0.0, cy=0.0, cz=0.0, label="ConeX"):
    r1 = d1 / 2.0
    r2 = d2 / 2.0
    cone = Part.makeCone(r1, r2, L)
    cone.Placement = App.Placement(App.Vector(cx - L/2.0, cy, cz), rot_to_x())
    return add_obj(cone, label)

def make_box(w, d, h, cx=0.0, cy=0.0, cz=0.0, label="Box"):
    b = Part.makeBox(w, d, h)
    b.Placement = App.Placement(App.Vector(cx - w/2.0, cy - d/2.0, cz - h/2.0), App.Rotation())
    return add_obj(b, label)

def make_hollow_cyl(d_out, d_in, h):
    return Part.makeCylinder(d_out/2.0, h).cut(Part.makeCylinder(d_in/2.0, h))

def fillet_between(shpA, shpB, r):
    fused = shpA.fuse(shpB)
    try:
        edges = [e for e in fused.Edges if e.Length > 60 and e.Length < 20000]
        new = fused.makeFillet(r, edges)
        return new
    except Exception:
        return fused

# ========================
# Construcción del fuselaje
# ========================
nose = make_cone_x(P["nose_base_d"], 0.0, P["nose_len"], cx=P["nose_len"]/2.0, label="Nose")
set_mat(nose, 'TITANIUM')

mid = make_cyl_x(P["mid_d"], P["mid_len"], cx=P["nose_len"] + P["mid_len"]/2.0, label="Mid")
set_mat(mid, 'CARBON_FIBER')

rear = make_cyl_x(P["rear_d"], P["rear_len"], cx=P["nose_len"] + P["mid_len"] + P["rear_len"]/2.0, label="Rear")
set_mat(rear, 'TITANIUM')

fuse_fuselage_shape = nose.Shape.fuse(mid.Shape).fuse(rear.Shape)
hull = Part.makeCylinder(P["mid_d"]/2.0, P["nose_len"] + P["mid_len"] + P["rear_len"])
hull.Placement = App.Placement(App.Vector(0, 0, 0), rot_to_x())
hull = hull.cut(Part.makeCylinder(P["mid_d"]/2.0 - P["hull_t"], P["nose_len"] + P["mid_len"] + P["rear_len"] + 10))
hull_obj = add_obj(hull, "Hull_Shell")
set_mat(hull_obj, 'CARBON_FIBER')

# Ventanas
win1 = make_box(P["win_w"], P["win_th"], P["win_h"], cx=P["cockpit_x0"] + P["cockpit_l"]/2.0, cy=(P["mid_d"]/2.0) - P["win_th"]/2.0, cz=0.0, label="Win_Right")
win2 = make_box(P["win_w"], P["win_th"], P["win_h"], cx=P["cockpit_x0"
] + P["cockpit_l"]/2.0, cy=-(P["mid_d"]/2.0) + P["win_th"]/2.0, cz=0.0, label="Win_Left")
hull_cut = add_obj(hull_obj.Shape.cut(win1.Shape).cut(win2.Shape), "Hull_Shell_Cut")
set_mat(hull_cut, 'CARBON_FIBER')

cockpit = make_box(P["cockpit_l"], P["cockpit_w"], P["cockpit_h"], cx=P["cockpit_x0"], cy=0.0, cz=0.0, label="Cockpit")
set_mat(cockpit, 'TITANIUM')

# ========================
# TPS avanzado con ablative
# ========================
nose_tip_x = P["nose_len"]
tps_support = make_cone_x(TPS["sup_d_base"], TPS["sup_d_tip"], TPS["sup_L"], cx=nose_tip_x + TPS["tps_gap"] + TPS["sup_L"]/2.0, label="TPS_Support")
set_mat(tps_support, 'TITANIUM')

tps_disk = make_cyl_x(TPS["tps_d"], TPS["tps_t"], cx=nose_tip_x + TPS["tps_gap"] + TPS["sup_L"] + TPS["tps_t"]/2.0, label="TPS_Shield")
set_mat(tps_disk, 'ABLATIVE')

TPS_fused_shape = fillet_between(tps_support.Shape, tps_disk.Shape, r=80.0)
TPS_fused = add_obj(TPS_fused_shape, "TPS_Assembly")
set_mat(TPS_fused, 'ABLATIVE')

# ========================
# Blindaje de radiación
# ========================
rad_shield = make_hollow_cyl(P["mid_d"] + 800.0, P["mid_d"] + 100.0, P["nose_len"] + P["mid_len"] + P["rear_len"] + 2000.0)
rad_shield.Placement = App.Placement(App.Vector((P["nose_len"] + P["mid_len"] + P["rear_len"])/2.0 - (P["nose_len"] + P["mid_len"] + P["rear_len"] + 2000.0)/2.0, 0, 0), rot_to_x())
rad_shield_obj = add_obj(rad_shield, "Radiation_Shield")
set_mat(rad_shield_obj, 'LEAD')

# ========================
# Reactor y sistemas
# ========================
reactor = make_cyl_x(P["reactor_d"], P["reactor_l"], cx=P["reactor_cx"], label="ReactorCore")
set_mat(reactor, 'TITANIUM')

# Anillos y bobinas (simplificados)
rings_shape = Part.makeTorus((P["ring_ro"] + P["ring_ri"])/2.0, (P["ring_ro"] - P["ring_ri"])/2.0)
rings_shape.Placement = App.Placement(App.Vector(P["reactor_cx"], 0, 0), rot_to_x())
rings_obj = add_obj(rings_shape, "Reactor_Rings")
set_mat(rings_obj, 'STEEL')

coils_obj = add_obj(Part.makeCylinder(200.0, P["coil_span"]), "Reactor_Coils")  # Simplificado
set_mat(coils_obj, 'COPPER')

# Tobera
noz = Part.makeCone(P["nozzle_throat_d"]/2.0, P["nozzle_exit_d"]/2.0, P["nozzle_l"])
noz.Placement = App.Placement(App.Vector(P["nozzle_cx"] - P["nozzle_l"]/2.0, 0, 0), rot_to_x())
noz_obj = add_obj(noz, "Magnetic_Nozzle")
set_mat(noz_obj, 'TITANIUM')

# ========================
# Características espaciales
# ========================
# Vela solar
solar_sail = make_box(6000.0, 5000.0, 10.0, cx=P["nose_len"] + P["mid_len"] + P["rear_len"] + 3000.0, cy=0.0, cz=0.0, label="Solar_Sail")
set_mat(solar_sail, 'CARBON_FIBER')

# Antena grande
large_antenna = make_cyl_x(1600.0, 50.0, cx=P["nose_len"] + P["mid_len"] + P["rear_len"] - 2000.0, label="Large_Antenna")
set_mat(large_antenna, 'CARBON_FIBER')

# Propulsores de actitud
attitude_thrusters = []
for i in range(8):
    angle = i * 45.0
    x = P["nose_len"] + P["mid_len"]/2.0
    y = 2000.0 * math.cos(math.radians(angle))
    z = 2000.0 * math.sin(math.radians(angle))
    thruster = make_cyl_x(300.0, 400.0, cx=x, cy=y, cz=z, label=f"Attitude_Thruster_{i+1}")
    set_mat(thruster, 'TITANIUM')
    attitude_thrusters.append(thruster)

# Paneles solares
solar_panels = []
for i in range(8):
    panel = make_box(4000.0, 100.0, 3000.0, cx=P["nose_len"] + P["mid_len"]/2.0 + i*500.0, cy=(P["mid_d"]/2.0 + 500.0) * (-1 if i % 2 else 1), cz=0.0, label=f"Solar_Panel_{i+1}")
    set_mat(panel, 'CARBON_FIBER')
    solar_panels.append(panel)

# ========================
# Ensamblado final
# ========================
to_fuse = [hull_cut, cockpit, TPS_fused, nose, mid, rear, reactor, rings_obj, coils_obj, noz_obj, rad_shield_obj, solar_sail, large_antenna] + attitude_thrusters + solar_panels

fused = to_fuse[0].Shape
for o in to_fuse[1:]:
    try:
        fused = fused.fuse(o.Shape)
    except Exception:
        pass

Assembly_Fused = add_obj(fused, "Spaceship_Assembly")
set_mat(Assembly_Fused, 'CARBON_FIBER')

doc.recompute()
print("Nave espacial Direct Fusion completada: Assembly_Fused (pieza única imprimible en Cura), con blindaje de radiación, TPS avanzado, vela solar, antena grande, propulsores de actitud y paneles solares. Lista para lanzamiento al espacio exterior.")
