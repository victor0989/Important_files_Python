# -*- coding: utf-8 -*-
# Estación "Parker XL" — macro ejecutable con blindaje y supervivencia ampliados

import FreeCAD as App
import Part
import math

try:
    import FreeCADGui as Gui
    HAS_GUI = True
except Exception:
    HAS_GUI = False

DOC_NAME = "Parker_XL_Defense"

# ----------------------------------------------------
# Utilidades
# ----------------------------------------------------
def mm(x_m):
    return float(x_m) * 1000.0

def ensure_doc(name=DOC_NAME):
    if App.ActiveDocument and App.ActiveDocument.Name == name:
        doc = App.ActiveDocument
        for o in list(doc.Objects):
            try:
                doc.removeObject(o.Name)
            except Exception:
                pass
        return doc
    for d in list(App.listDocuments().values()):
        if d.Name == name:
            App.closeDocument(d.Name)
    return App.newDocument(name)

def add_obj(shape, name, color=None, transparency=0):
    obj = App.ActiveDocument.addObject("Part::Feature", name)
    obj.Shape = shape
    if HAS_GUI:
        try:
            if color is not None:
                obj.ViewObject.ShapeColor = color
            obj.ViewObject.Transparency = int(transparency)
        except Exception:
            pass
    return obj

def fuse_all(shapes):
    shapes = [s for s in shapes if s is not None]
    if not shapes:
        return None
    s = shapes[0]
    for t in shapes[1:]:
        try:
            s = s.fuse(t)
        except Exception:
            pass
    return s

def cut_safe(a, b):
    if a is None:
        return None
    if b is None:
        return a
    try:
        return a.cut(b)
    except Exception:
        return a

def rotate(shape, axis, angle_deg, center=App.Vector(0,0,0)):
    sh = shape.copy()
    sh.rotate(center, axis, angle_deg)
    return sh

def translate(shape, v):
    sh = shape.copy()
    sh.translate(v)
    return sh

def box_centered(cx, cy, cz, lx, ly, lz):
    # Caja centrada en (cx,cy,cz) con dimensiones lx,ly,lz (en mm)
    return Part.makeBox(lx, ly, lz, App.Vector(cx - lx/2.0, cy - ly/2.0, cz - lz/2.0))

# ----------------------------------------------------
# Parámetros (metros)
# ----------------------------------------------------
P = dict(
    crew = 22,

    # Campana (secciones rectangulares YZ)
    campana_front_w = 64.0,
    campana_front_h = 44.0,
    campana_back_w  = 48.0,
    campana_back_h  = 30.0,
    campana_depth   = 3.5,
    campana_wall_t  = 0.9,
    lip_w           = 0.6,
    lip_t           = 0.2,

    # Aros rectangulares detrás del TPS
    ring_gap        = 2.0,
    ring_thick      = 0.8,
    ring_width      = 1.2,
    ring2_offset    = 2.5,

    # Hex-ring estructural
    hex_outer_R     = 18.0,
    hex_inner_R     = 15.5,
    hex_thick       = 1.2,
    hex_x           = -8.0,

    # Bus principal
    bus_len  = 48.0,
    bus_w    = 10.0,
    bus_h    = 10.0,
    bus_x    = -35.0,

    # Paneles solares
    panel_len = 36.0,
    panel_w   = 8.0,
    panel_th  = 0.12,
    panel_x   = -32.0,
    panel_gap = 2.0,
    panel_grid_ny = 24,
    panel_grid_nz = 8,
    panel_groove  = 0.01,

    # Radiadores
    rad_count = 4,
    rad_len = 14.0,
    rad_w   = 4.0,
    rad_th  = 0.10,
    rad_x   = -46.0,
    rad_z   = 7.0,
    rad_fan_angle = 40.0,

    # Tanques laterales
    tank_r = 1.4,
    tank_l = 10.0,
    tank_offset_y = 8.0,
    tank_x = -36.0,

    # RCS
    rcs_cone_r1 = 0.35,
    rcs_cone_r2 = 0.10,
    rcs_cone_h = 0.8,

    # Star trackers
    st_box = (1.0, 0.8, 0.8),
    st_lens_r = 0.25,
    st_x = -30.0,
    st_y = 6.0,
    st_z = 4.0,

    # Antenas
    dish_r = 2.2,
    dish_h = 0.9,
    dish_x = -40.0,
    whip_len = 16.0,
    whip_r   = 0.05,

    # Boom instrumentos
    boom_len = 20.0,
    boom_r   = 0.35,
    boom_x0  = -55.0,
    boom_angle = -10.0,

    # Detalles TPS
    bolt_count = 80,
    bolt_r = 0.12,
    bolt_l = 0.28,
    visor_span = 1.6,
    visor_w = 1.2,
    visor_l = 0.8,
    visor_th = 0.05,

    # Blindaje Whipple alrededor del bus
    whipple_gap = 0.6,          # separación entre bus y pantalla
    whipple_skin = 0.06,         # espesor de piel exterior
    whipple_strut = 0.08,        # puntales
    whipple_frames = 6,          # marcos a lo largo de X

    # Blindaje tanques (faldas y arcos)
    tank_skirt_t = 0.10,
    tank_arc_r = 1.9,
    tank_arc_t = 0.08,

    # Parachoques frontal y aro corta-rocas
    bumper_offset_x = 0.6,
    bumper_bar_t = 0.12,
    bumper_bar_w = 1.0,
    cutter_ring_t = 0.25,
    cutter_ring_w = 1.2,
    cutter_blade_len = 2.2,
    cutter_blade_t = 0.10,
    cutter_blade_count = 12,

    # Brazos robóticos
    arm_base_x = -20.0,
    arm_base_y = 7.0,
    arm_base_z = 0.0,
    arm_seg_r = 0.30,
    arm_seg1_l = 6.0,
    arm_seg2_l = 5.0,
    arm_tool_len = 1.2,

    # Drones interceptores (anclados bajo radiadores)
    drone_count = 2,
    drone_body = (1.6, 1.0, 0.6),
    drone_thr_r = 0.16,
    drone_thr_l = 0.5,

    # Ultrasensores
    lidar_r = 0.8,
    lidar_h = 0.4,
    radar_panel = (4.0, 0.12, 3.0),
    ir_tube_r = 0.45,
    ir_tube_l = 2.2,
    aux_antenna_r = 0.10,
    aux_antenna_l = 6.0
)

# ----------------------------------------------------
# Constructores base
# ----------------------------------------------------
def rect_wire_yz(w_m, h_m, x_m):
    w = mm(w_m); h = mm(h_m); x = mm(x_m)
    hw, hh = w/2.0, h/2.0
    pts = [
        App.Vector(x, -hw, -hh),
        App.Vector(x,  hw, -hh),
        App.Vector(x,  hw,  hh),
        App.Vector(x, -hw,  hh),
        App.Vector(x, -hw, -hh),
    ]
    return Part.makePolygon(pts)

def make_tps_campana(P):
    fw, fh = P["campana_front_w"], P["campana_front_h"]
    bw, bh = P["campana_back_w"],  P["campana_back_h"]
    depth  = P["campana_depth"]
    wall_t = P["campana_wall_t"]
    lipw   = P["lip_w"]; lipt = P["lip_t"]

    wf = rect_wire_yz(fw, fh, 0.0)
    wb = rect_wire_yz(bw, bh, -depth)
    loft_ext = Part.makeLoft([wf, wb], True, False, False)

    eps = 0.02
    if fw - 2*wall_t <= 0 or fh - 2*wall_t <= 0 or bw - 2*wall_t <= 0 or bh - 2*wall_t <= 0:
        wall_t = min(wall_t, min(fw, fh, bw, bh) * 0.2)
    wfi = rect_wire_yz(max(0.1, fw - 2*wall_t), max(0.1, fh - 2*wall_t), -eps)
    wbi = rect_wire_yz(max(0.1, bw - 2*wall_t), max(0.1, bh - 2*wall_t), -depth + eps)
    loft_int = Part.makeLoft([wfi, wbi], True, False, False)

    shell = cut_safe(loft_ext, loft_int)

    lip_outer = Part.Face(rect_wire_yz(fw, fh, 0.0))
    lip_inner = Part.Face(rect_wire_yz(max(0.1, fw - 2*lipw), max(0.1, fh - 2*lipw), 0.0))
    lip_face = cut_safe(lip_outer, lip_inner)
    lip = lip_face.extrude(App.Vector(mm(lipt), 0, 0))

    def ring_at(x_m):
        outer = Part.Face(rect_wire_yz(bw, bh, x_m))
        inner = Part.Face(rect_wire_yz(max(0.1, bw - 2*P["ring_width"]), max(0.1, bh - 2*P["ring_width"]), x_m))
        face  = cut_safe(outer, inner)
        return face.extrude(App.Vector(mm(P["ring_thick"]), 0, 0))

    ring1 = ring_at(-P["ring_gap"])
    ring2 = ring_at(-P["ring_gap"] - P["ring2_offset"] - P["ring_thick"])

    return fuse_all([shell, lip, ring1, ring2])

def make_bolts_rect_perimeter(P):
    fw, fh = mm(P["campana_front_w"]), mm(P["campana_front_h"])
    n = P["bolt_count"]; r = mm(P["bolt_r"]); L = mm(P["bolt_l"])
    half_w, half_h = fw/2.0, fh/2.0
    bolts = []
    per = 2*(fw + fh)
    step = per / n
    dist = 0.0
    for _ in range(n):
        p = dist % per
        if p < fw:
            y = -half_w + p; z = half_h
        elif p < fw + fh:
            y = half_w; z = half_h - (p - fw)
        elif p < 2*fw + fh:
            y = half_w - (p - (fw + fh)); z = -half_h
        else:
            y = -half_w; z = -half_h + (p - (2*fw + fh))
        cyl = Part.makeCylinder(r, L, App.Vector(-mm(0.05), y, z), App.Vector(1,0,0))
        bolts.append(cyl)
        dist += step
    return fuse_all(bolts)

def make_edge_visors_rect(P):
    fw, fh = mm(P["campana_front_w"]), mm(P["campana_front_h"])
    half_w, half_h = fw/2.0, fh/2.0
    span = mm(P["visor_span"]); vw = mm(P["visor_w"]); vl = mm(P["visor_l"]); th = mm(P["visor_th"])
    vis = []
    count_top = max(2, int(fw / span))
    for i in range(count_top):
        y = -half_w + (i + 0.5) * (fw / count_top)
        box = Part.makeBox(th, vw, vl, App.Vector(0, y - vw/2.0, half_h - vl/2.0))
        vis.append(box)
    count_bot = count_top
    for i in range(count_bot):
        y = -half_w + (i + 0.5) * (fw / count_bot)
        box = Part.makeBox(th, vw, vl, App.Vector(0, y - vw/2.0, -half_h - vl/2.0))
        vis.append(box)
    count_right = max(2, int(fh / span))
    for i in range(count_right):
        z = -half_h + (i + 0.5) * (fh / count_right)
        box = Part.makeBox(th, vw, vl, App.Vector(0, half_w - vw/2.0, z - vl/2.0))
        vis.append(box)
    count_left = count_right
    for i in range(count_left):
        z = -half_h + (i + 0.5) * (fh / count_left)
        box = Part.makeBox(th, vw, vl, App.Vector(0, -half_w - vw/2.0, z - vl/2.0))
        vis.append(box)
    return fuse_all(vis)

def make_hex_ring(P):
    R_out = mm(P["hex_outer_R"])
    R_in  = mm(P["hex_inner_R"])
    t     = mm(P["hex_thick"])
    x0    = mm(P["hex_x"])
    def hex_wire(R):
        pts = []
        for k in range(6):
            ang = math.radians(60*k + 30)
            y = R * math.cos(ang)
            z = R * math.sin(ang)
            pts.append(App.Vector(x0, y, z))
        pts.append(pts[0])
        return Part.makePolygon(pts)
    outer_w = hex_wire(R_out)
    inner_w = hex_wire(R_in)
    face_outer = Part.Face(outer_w)
    face_inner = Part.Face(inner_w)
    ring_face = cut_safe(face_outer, face_inner)
    return ring_face.extrude(App.Vector(t, 0, 0))

def make_bus(P):
    L = mm(P["bus_len"]); W = mm(P["bus_w"]); H = mm(P["bus_h"]); x = mm(P["bus_x"])
    bus = Part.makeBox(L, W, H, App.Vector(x - L/2.0, -W/2.0, -H/2.0))
    try:
        bus = bus.makeChamfer(mm(0.6), bus.Edges)
    except Exception:
        pass
    return bus

def make_tanks(P):
    r = mm(P["tank_r"]); l = mm(P["tank_l"]); x = mm(P["tank_x"]); oy = mm(P["tank_offset_y"])
    left  = Part.makeCylinder(r, l, App.Vector(x - l/2.0, -oy, 0), App.Vector(1,0,0))
    right = Part.makeCylinder(r, l, App.Vector(x - l/2.0,  oy, 0), App.Vector(1,0,0))
    return fuse_all([left, right])

def make_panels_with_grid(P, side=+1):
    L = mm(P["panel_len"]); W = mm(P["panel_w"]); TH = mm(P["panel_th"])
    x = mm(P["panel_x"]); gap = mm(P["panel_gap"])
    y0 = side * (mm(P["bus_w"])/2.0 + gap)
    base_th = mm(0.60)
    plate_th = TH
    base  = Part.makeBox(base_th, L, W, App.Vector(x - base_th/2.0, y0 - L/2.0, -W/2.0))
    plate = Part.makeBox(plate_th, L, W, App.Vector(x + base_th/2.0, y0 - L/2.0, -W/2.0))
    panel = fuse_all([base, plate])
    ny, nz = max(2, P["panel_grid_ny"]), max(2, P["panel_grid_nz"])
    gy = L / ny; gz = W / nz
    groove = mm(P["panel_groove"])
    groove = min(groove, plate_th - mm(0.001))
    groove_x0 = x + base_th/2.0 + (plate_th - groove)
    grooves = []
    cut_wY = mm(0.05)
    for i in range(1, ny):
        y_pos = y0 - L/2.0 + i*gy - cut_wY/2.0
        g = Part.makeBox(groove, cut_wY, W, App.Vector(groove_x0, y_pos, -W/2.0))
        grooves.append(g)
    cut_wZ = mm(0.05)
    for j in range(1, nz):
        z_pos = -W/2.0 + j*gz - cut_wZ/2.0
        g = Part.makeBox(groove, L, cut_wZ, App.Vector(groove_x0, y0 - L/2.0, z_pos))
        grooves.append(g)
    if grooves:
        panel = cut_safe(panel, fuse_all(grooves))
    return panel

def make_radiators(P):
    plates = []
    L = mm(P["rad_len"]); W = mm(P["rad_w"]); TH = mm(P["rad_th"])
    x = mm(P["rad_x"]); z = mm(P["rad_z"])
    n = P["rad_count"]; fan = P["rad_fan_angle"]
    for i in range(n):
        angle = -fan/2.0 + (fan * (i / float(max(1, n-1))))
        plate = Part.makeBox(TH, L, W, App.Vector(x - TH/2.0, -L/2.0, z))
        plate = rotate(plate, App.Vector(1,0,0), angle, App.Vector(x, 0, z))
        plates.append(plate)
    return fuse_all(plates)

def make_rcs(P, bus_shape):
    r1 = mm(P["rcs_cone_r1"]); r2 = mm(P["rcs_cone_r2"]); h = mm(P["rcs_cone_h"])
    bb = bus_shape.BoundBox
    cones = []
    for sgnY in (+1, -1):
        for sgnZ in (+1, -1):
            for xi in (bb.XMin + mm(2.0), bb.XMax - mm(2.0)):
                y = sgnY * (P["bus_w"]/2.0 + P["panel_gap"]/2.0)
                z = sgnZ * (P["bus_h"]/2.0 - 1.0)
                cone = Part.makeCone(r1, r2, h, App.Vector(xi, mm(y), mm(z)), App.Vector(0, 1, 0))
                if sgnY < 0:
                    cone = rotate(cone, App.Vector(0,0,1), 180, App.Vector(xi, mm(y), mm(z)))
                cones.append(cone)
    return fuse_all(cones)

def make_star_trackers(P):
    bx, by, bz = [mm(v) for v in P["st_box"]]
    x = mm(P["st_x"]); y = mm(P["st_y"]); z = mm(P["st_z"])
    body1 = Part.makeBox(bx, by, bz, App.Vector(x - bx/2.0, y - by/2.0, z - bz/2.0))
    lens1 = Part.makeCylinder(mm(P["st_lens_r"]), mm(0.4), App.Vector(x + bx/2.0, y, z), App.Vector(1,0,0))
    body2 = Part.makeBox(bx, by, bz, App.Vector(x - bx/2.0, -y - by/2.0, -z - bz/2.0))
    lens2 = Part.makeCylinder(mm(P["st_lens_r"]), mm(0.4), App.Vector(x + bx/2.0, -y, -z), App.Vector(1,0,0))
    return fuse_all([body1, lens1, body2, lens2])

def make_dish_and_whips(P):
    r = mm(P["dish_r"]); h = mm(P["dish_h"]); x = mm(P["dish_x"])
    dish = Part.makeCone(r, r*0.15, h, App.Vector(x - h, 0, 0), App.Vector(1,0,0))
    mast = Part.makeCylinder(mm(0.18), mm(3.0), App.Vector(x + mm(0.2), 0, 0), App.Vector(1,0,0))
    whipL = Part.makeCylinder(mm(P["whip_r"]), mm(P["whip_len"]), App.Vector(x, mm(2.0), 0), App.Vector(0,1,0))
    whipR = Part.makeCylinder(mm(P["whip_r"]), mm(P["whip_len"]), App.Vector(x, -mm(2.0), 0), App.Vector(0,-1,0))
    return fuse_all([dish, mast, whipL, whipR])

def make_boom(P):
    L = mm(P["boom_len"]); r = mm(P["boom_r"]); x0 = mm(P["boom_x0"])
    tube = Part.makeCylinder(r, L, App.Vector(x0, 0, 0), App.Vector(1,0,0))
    tube = rotate(tube, App.Vector(0,1,0), P["boom_angle"], App.Vector(x0,0,0))
    return tube

# ----------------------------------------------------
# Nuevos módulos de defensa y supervivencia
# ----------------------------------------------------
def make_whipple_shield(P, bus_shape):
    # Marcos rectangulares separados del bus, con piel exterior y puntales
    bb = bus_shape.BoundBox
    gap = mm(P["whipple_gap"])
    skin = mm(P["whipple_skin"])
    frames = P["whipple_frames"]
    strut = mm(P["whipple_strut"])

    L = bb.XLength + mm(0.5)
    W = bb.YLength + 2*gap
    H = bb.ZLength + 2*gap

    x0 = (bb.XMin + bb.XMax)/2.0
    x_min = x0 - L/2.0
    shield = []

    # Piel exterior (caja hueca muy fina por Y/Z, larga en X)
    outer = Part.makeBox(L, W + 2*skin, H + 2*skin, App.Vector(x_min, bb.YMin - gap - skin, bb.ZMin - gap - skin))
    inner = Part.makeBox(L, W - 2*skin, H - 2*skin, App.Vector(x_min, bb.YMin - gap + skin, bb.ZMin - gap + skin))
    shell = cut_safe(outer, inner)
    shield.append(shell)

    # Marcos intermedios
    for i in range(frames):
        tx = x_min + (i + 0.5) * (L / frames)
        frame = box_centered(tx, 0, 0, mm(0.10), W, H)
        # abrir ventana central para permitir disipación
        window = box_centered(tx, 0, 0, mm(0.12), W - mm(0.6), H - mm(0.6))
        frame = cut_safe(frame, window)
        shield.append(frame)

    # Puntales (en Z+ y Z- hacia la piel)
    for sgnZ in (+1, -1):
        for sgnY in (+1, -1):
            for i in range(frames):
                tx = x_min + (i + 0.5) * (L / frames)
                y = sgnY * (bb.YLength/2.0 + gap/2.0)
                z = sgnZ * (bb.ZLength/2.0 + gap/2.0)
                st = box_centered(tx, y, z, mm(0.5), strut, strut)
                shield.append(st)

    return fuse_all(shield)

def make_tank_armor(P, tanks_shape):
    # Faldas laterales y arcos superiores protectores sobre cada tanque
    r = mm(P["tank_r"]); l = mm(P["tank_l"])
    t = mm(P["tank_skirt_t"])
    arc_r = mm(P["tank_arc_r"]); arc_t = mm(P["tank_arc_t"])
    bb = tanks_shape.BoundBox

    # Separar tanques en dos aproximando por bounding box en Y
    midY = (bb.YMin + bb.YMax)/2.0
    # Faldas (cajas) a cada lado
    skirt_left  = Part.makeBox(l + mm(0.6), t, 2*r + mm(0.6),
                               App.Vector(bb.XMin - mm(0.3), bb.YMin - t - mm(0.2), -r - mm(0.3)))
    skirt_right = Part.makeBox(l + mm(0.6), t, 2*r + mm(0.6),
                               App.Vector(bb.XMin - mm(0.3), bb.YMax + mm(0.2), -r - mm(0.3)))
    # Arcos superiores (aprox con cilindros tumbados cortados)
    arc_len = l + mm(0.6)
    ax = bb.XMin - mm(0.3)
    arcL = Part.makeCylinder(arc_r, arc_len, App.Vector(ax, midY - mm(P["tank_offset_y"]), 0), App.Vector(1,0,0))
    arcL = cut_safe(arcL, Part.makeCylinder(arc_r - arc_t, arc_len + mm(1.0), App.Vector(ax - mm(0.5), midY - mm(P["tank_offset_y"]), 0), App.Vector(1,0,0)))
    arcR = Part.makeCylinder(arc_r, arc_len, App.Vector(ax, midY + mm(P["tank_offset_y"]) - mm(2.0*P["tank_offset_y"]), 0), App.Vector(1,0,0))
    arcR = cut_safe(arcR, Part.makeCylinder(arc_r - arc_t, arc_len + mm(1.0), App.Vector(ax - mm(0.5), midY + mm(P["tank_offset_y"]) - mm(2.0*P["tank_offset_y"]), 0), App.Vector(1,0,0)))

    return fuse_all([skirt_left, skirt_right, arcL, arcR])

def make_front_bumper_and_cutter(P):
    # Rejilla cruzada delante de la boca + aro con cuchillas
    fw = mm(P["campana_front_w"]); fh = mm(P["campana_front_h"])
    half_w, half_h = fw/2.0, fh/2.0
    offx = mm(P["bumper_offset_x"])
    bar_t = mm(P["bumper_bar_t"]); bar_w = mm(P["bumper_bar_w"])

    bars = []
    # Barras horizontales
    for z in (-half_h*0.5, 0, half_h*0.5):
        bar = Part.makeBox(bar_t, fw, bar_w, App.Vector(offx, -half_w, z - bar_w/2.0))
        bars.append(bar)
    # Barras verticales
    for y in (-half_w*0.5, 0, half_w*0.5):
        bar = Part.makeBox(bar_t, bar_w, fh, App.Vector(offx, y - bar_w/2.0, -half_h))
        bars.append(bar)
    grill = fuse_all(bars)

    # Aro rectangular alrededor del borde con cuchillas radiales
    ring_t = mm(P["cutter_ring_t"]); ring_w = mm(P["cutter_ring_w"])
    ring_outer = Part.Face(rect_wire_yz(P["campana_front_w"] + 2*P["cutter_ring_w"], P["campana_front_h"] + 2*P["cutter_ring_w"], P["bumper_offset_x"]))
    ring_inner = Part.Face(rect_wire_yz(P["campana_front_w"], P["campana_front_h"], P["bumper_offset_x"]))
    ring_face = cut_safe(ring_outer, ring_inner)
    ring = ring_face.extrude(App.Vector(ring_t, 0, 0))

    blades = []
    nB = max(4, int(P["cutter_blade_count"]))
    for k in range(nB):
        ang = 360.0 * k / float(nB)
        # Cuchilla como caja larga orientada hacia fuera
        b_len = mm(P["cutter_blade_len"])
        b_t   = mm(P["cutter_blade_t"])
        # Colocar base en el borde del rectángulo mayor (aprox usando radio circunscrito)
        R = max(half_w, half_h) + mm(P["cutter_ring_w"]) + b_len/2.0
        cy = R * math.cos(math.radians(ang))
        cz = R * math.sin(math.radians(ang))
        blade = box_centered(mm(P["bumper_offset_x"]) + ring_t/2.0, cy, cz, ring_t, b_t, b_len)
        blade = rotate(blade, App.Vector(0,0,1), ang, App.Vector(mm(P["bumper_offset_x"]), 0, 0))
        blades.append(blade)

    cutter = fuse_all([ring, fuse_all(blades)])
    return fuse_all([grill, cutter])

def make_robot_arm(P, side=+1):
    # Brazo de dos segmentos con herramienta dual (sierra + láser)
    base_x = mm(P["arm_base_x"])
    base_y = side * mm(P["arm_base_y"])
    base_z = mm(P["arm_base_z"])
    r = mm(P["arm_seg_r"])
    L1 = mm(P["arm_seg1_l"])
    L2 = mm(P["arm_seg2_l"])
    toolL = mm(P["arm_tool_len"])

    # Base rotativa
    base = Part.makeCylinder(r*0.9, mm(0.6), App.Vector(base_x, base_y, base_z - r), App.Vector(1,0,0))

    # Segmento 1 (eleva en Z)
    seg1 = Part.makeCylinder(r, L1, App.Vector(base_x + mm(0.6), base_y, base_z), App.Vector(0,0,1))
    # Articulación esférica
    j1 = Part.makeSphere(r*1.05, App.Vector(base_x + mm(0.6), base_y, base_z + L1))

    # Segmento 2 (se extiende hacia X)
    seg2 = Part.makeCylinder(r*0.9, L2, App.Vector(base_x + mm(0.6), base_y, base_z + L1), App.Vector(1,0,0))

    # Herramientas: sierra circular y emisor láser coaxial
    saw_R = r*1.2
    saw = Part.makeCylinder(saw_R, mm(0.15), App.Vector(base_x + mm(0.6) + L2, base_y, base_z + L1 - saw_R), App.Vector(0,0,1))
    laser = Part.makeCone(mm(0.18), mm(0.05), toolL, App.Vector(base_x + mm(0.6) + L2, base_y, base_z + L1), App.Vector(1,0,0))

    # Garra simple
    jaw1 = Part.makeBox(mm(0.2), mm(0.8), mm(0.12), App.Vector(base_x + mm(0.6) + L2 + toolL - mm(0.1), base_y - mm(0.4), base_z + L1 - mm(0.06)))
    jaw2 = Part.makeBox(mm(0.2), mm(0.8), mm(0.12), App.Vector(base_x + mm(0.6) + L2 + toolL - mm(0.1), base_y - mm(0.4), base_z + L1 + mm(0.06)))

    return fuse_all([base, seg1, j1, seg2, saw, laser, jaw1, jaw2])

def make_drones(P, anchor_x, anchor_z):
    # Drones compactos con toberas RCS y cuchilla frontal
    n = P["drone_count"]
    bx, by, bz = [mm(v) for v in P["drone_body"]]
    thr_r = mm(P["drone_thr_r"]); thr_l = mm(P["drone_thr_l"])
    bots = []
    for i in range(n):
        dy = (-1)**i * mm(2.0) + (i*mm(1.2))
        body = box_centered(mm(anchor_x), dy, mm(anchor_z), bx, by, bz)
        nose = Part.makeCone(bx*0.25, bx*0.05, mm(0.6), App.Vector(mm(anchor_x) + bx/2.0, dy, mm(anchor_z)), App.Vector(1,0,0))
        # Toberas en cruz
        thrU = Part.makeCylinder(thr_r, thr_l, App.Vector(mm(anchor_x) - bx/2.0, dy, mm(anchor_z) + bz/2.0), App.Vector(0,0,1))
        thrD = Part.makeCylinder(thr_r, thr_l, App.Vector(mm(anchor_x) - bx/2.0, dy, mm(anchor_z) - bz/2.0 - thr_l), App.Vector(0,0,-1))
        thrL = Part.makeCylinder(thr_r, thr_l, App.Vector(mm(anchor_x) - bx/2.0, dy - by/2.0 - thr_l, mm(anchor_z)), App.Vector(0,1,0))
        thrR = Part.makeCylinder(thr_r, thr_l, App.Vector(mm(anchor_x) - bx/2.0, dy + by/2.0, mm(anchor_z)), App.Vector(0,1,0))
        blade = box_centered(mm(anchor_x) + bx/2.0 + mm(0.5), dy, mm(anchor_z), mm(0.8), mm(0.08), mm(0.4))
        bots.append(fuse_all([body, nose, thrU, thrD, thrL, thrR, blade]))
    return fuse_all(bots)

def make_ultra_sensors(P, bus_shape):
    bb = bus_shape.BoundBox
    # LIDAR: cúpula + base
    lidar_r = mm(P["lidar_r"]); lidar_h = mm(P["lidar_h"])
    lid_base = Part.makeCylinder(lidar_r*0.6, mm(0.2), App.Vector(bb.XMax - mm(4.0), 0, bb.ZMax + mm(0.1)), App.Vector(0,0,1))
    lid_dome = Part.makeSphere(lidar_r, App.Vector(bb.XMax - mm(4.0), 0, bb.ZMax + lidar_h))
    # Radar panel plano (X paralelo, cara en +Y lado derecho)
    rp_x = bb.XMin + mm(6.0)
    rp_w, rp_t, rp_h = [mm(v) for v in P["radar_panel"]]
    radar = Part.makeBox(rp_t, rp_w, rp_h, App.Vector(rp_x, bb.YMax + mm(0.5), -rp_h/2.0))
    # Telescopio IR (tubo) en mástil superior
    ir_r = mm(P["ir_tube_r"]); ir_l = mm(P["ir_tube_l"])
    ir = Part.makeCylinder(ir_r, ir_l, App.Vector(bb.XMin + mm(2.0), 0, bb.ZMax + mm(0.8)), App.Vector(1,0,0))
    # Antenas auxiliares (dos látigos)
    aux_r = mm(P["aux_antenna_r"]); aux_l = mm(P["aux_antenna_l"])
    a1 = Part.makeCylinder(aux_r, aux_l, App.Vector(bb.XMax - mm(3.0), bb.YMax + mm(0.6), 0), App.Vector(0,1,0))
    a2 = Part.makeCylinder(aux_r, aux_l, App.Vector(bb.XMax - mm(3.0), bb.YMin - mm(0.6), 0), App.Vector(0,-1,0))
    return fuse_all([lid_base, lid_dome, radar, ir, a1, a2])

# ----------------------------------------------------
# Ensamblado completo
# ----------------------------------------------------
def assemble_station(P):
    doc = ensure_doc()

    # TPS campana + detalles
    campana = make_tps_campana(P)
    add_obj(campana, "TPS_Campana", color=(0.20,0.20,0.22))

    bolts = make_bolts_rect_perimeter(P)
    add_obj(bolts, "TPS_Bolts", color=(0.65,0.65,0.65))

    visors = make_edge_visors_rect(P)
    add_obj(visors, "TPS_Visors", color=(0.30,0.30,0.32))

    # Hex ring
    hexring = make_hex_ring(P)
    add_obj(hexring, "Hex_Ring", color=(0.35,0.35,0.37))

    # Bus principal y tanques
    bus = make_bus(P)
    add_obj(bus, "Bus_Main", color=(0.22,0.24,0.28))

    tanks = make_tanks(P)
    add_obj(tanks, "Side_Tanks", color=(0.55,0.56,0.58))

    # Blindajes
    whipple = make_whipple_shield(P, bus)
    add_obj(whipple, "Shield_Whipple", color=(0.40,0.42,0.45), transparency=40)

    tankArmor = make_tank_armor(P, tanks)
    add_obj(tankArmor, "Shield_Tanks", color=(0.45,0.47,0.50))

    # Parachoques y aro corta-rocas
    bumper = make_front_bumper_and_cutter(P)
    add_obj(bumper, "Front_Bumper_Cutter", color=(0.55,0.55,0.58))

    # Paneles
    panelR = make_panels_with_grid(P, side=+1)
    add_obj(panelR, "Solar_Right", color=(0.06,0.16,0.25))
    panelL = make_panels_with_grid(P, side=-1)
    add_obj(panelL, "Solar_Left", color=(0.06,0.16,0.25))

    # Radiadores
    rads = make_radiators(P)
    add_obj(rads, "Radiators", color=(0.85,0.85,0.90))

    # RCS
    rcs = make_rcs(P, bus)
    add_obj(rcs, "RCS_Thrusters", color=(0.45,0.45,0.48))

    # Star trackers
    st = make_star_trackers(P)
    add_obj(st, "Star_Trackers", color=(0.70,0.70,0.75))

    # Antenas principales
    comms = make_dish_and_whips(P)
    add_obj(comms, "Comms", color=(0.78,0.78,0.80))

    # Boom instrumentos
    boom = make_boom(P)
    add_obj(boom, "Instrument_Boom", color=(0.60,0.60,0.62))

    # Brazos robóticos (dos, simétricos)
    armR = make_robot_arm(P, side=+1)
    add_obj(armR, "Robot_Arm_Right", color=(0.58,0.58,0.60))
    armL = make_robot_arm(P, side=-1)
    add_obj(armL, "Robot_Arm_Left", color=(0.58,0.58,0.60))

    # Drones bajo radiadores
    drones = make_drones(P, anchor_x=P["rad_x"] + 2.0, anchor_z=P["rad_z"] - 1.0)
    add_obj(drones, "Interceptor_Drones", color=(0.50,0.52,0.55))

    # Ultrasensores
    sensors = make_ultra_sensors(P, bus)
    add_obj(sensors, "Ultra_Sensors", color=(0.75,0.76,0.78))

    doc.recompute()
    if HAS_GUI:
        try:
            Gui.SendMsgToActiveView("ViewFit")
            Gui.activeDocument().activeView().viewAxonometric()
        except Exception:
            pass

# Ejecutar
if __name__ == "__main__":
    assemble_station(P)
